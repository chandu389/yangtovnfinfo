module rmno-common {
  namespace "urn:rakuten:rmno:common";
  prefix rmno-common;

  import ietf-yang-types {
    prefix yang;
  }
  import ietf-inet-types {
    prefix inet;
  }
  import tailf-common {
    prefix tailf;
  }
  import tailf-ncs {
    prefix ncs;
  }

  include rmno-types;

  grouping standard-action-response {
    leaf result {
      type boolean;
    }
    leaf info {
      type string;
    }
  }

  grouping cisco-epc-iftask-cores {
    leaf iftask-cores {
      status deprecated;
      type percent;
      default 50;
      description
       "Percentage of CPU cores to allocate to IFTASK
       (Internal Forwarder Task).";
    }
  }
  grouping cisco-epc-iftask-mcdma-cores {
    leaf iftask-mcdma-cores {
      status deprecated;
      type percent;
      default 50;
      description
        "Sets the number of cores assigned to Multi-channel
        Direct Memory Access (MCDMA) to be a percentage of
        total iftask cores.

        NOTE: When NUMA optimization is enabled and also this
        MCDMA core count setting is configured you must set
        iftask-cores to be an even number. This ensures that
        the MCDMA threads are evenly distributed across the
        NUMA nodes.";
    }
  }
  grouping cisco-epc-iftask-crypto-cores {
    leaf iftask-crypto-cores {
      type percent {
        range "0..50";
      }
      default 50;
      description
        "The percentages of iftask cores to allocate to crypto
        processing. The cores dedicated will be capped at 4.";
    }
  }

  grouping cisco-epc-cdr-storage-size {
    leaf cdr-storage-size {
        type int32 {
          range "0..max";
        }
        default 200;
        units GB;
    }
  }
  grouping cisco-epc-boot-storage-size {
    leaf boot-storage-size {
        type int32 {
          range "0..max";
        }
        default 32;
        units GB;
    }
  }

  grouping nokia-ims-hss-extensions {
    leaf cakey {
      type string;
      // type binary;
      description "CA Key generated by CMRepo";
      reference "Nokia HSS VNFD: VNF Extensions: cakey";
    }
    leaf dn {
      type string;
      description "Domain Name of the VNF";
      reference "Nokia HSS VNFD: VNF Extensions: dn";
    }
    leaf du {
      type string;
      description "Deployment Unit of the VNF";
      reference "Nokia HSS VNFD: VNF Extensions: du";
    }
    leaf cmrepo-ip {
      mandatory true;
      type inet:ip-address;
      description "CMRepo IP address";
      reference "Nokia HSS VNFD: VNF Extensions: cmrepo_ip";
    }
    leaf cmrepo-user {
      mandatory true;
      type rmno-common:identifier;
      description "CMRepo username";
      reference "Nokia HSS VNFD: VNF Extensions: cmrepo_user";
    }
    leaf cmrepo-password {
      mandatory true;
      type tailf:aes-cfb-128-encrypted-string;
      tailf:suppress-echo "true";
      description "CMRepo password";
      reference "Nokia HSS VNFD: VNF Extensions: cmrepo_password";
    }
    leaf swrepo-ip {
      type inet:ip-address;
      description
        "SWRepo IP address. Default value is to use same address
        as cmrepo.";
      reference "Nokia HSS VNFD: VNF Extensions: swrepo_ip";
      tailf:default-ref '../cmrepo-ip';
    }

    leaf aif {
      type string;
      default "no";
    }
    leaf health-check {
      type string;
      default "no";
    }
    leaf alb-vnic-count {
      type int32;
      default 6;
    }
    leaf overload-threshold-scale-in {
      type string;
      default 1;
    }
    leaf overload-threshold-scale-out {
      type string;
      default 2;
    }
    leaf oam-volume-size {
      type int32;
      default 300;
    }
    leaf storage-availability-zone1 {
      type string;
      default "nova";
    }
    leaf storage-availability-zone2 {
      type string;
      default "nova";
    }
    leaf dlb-vnic-count {
      type string;
      default "7";
    }
  }

  grouping nokia-ims-cmrepo-extensions {
    leaf netact-address {
      type inet:ip-address;
    }
    leaf aif {
      type string;
    }
    leaf storage-availability-zone1 {
      type string;
      default "uhn3kli1azovs1";
    }
    leaf storage-availability-zone2 {
      type string;
      default "uhn3kli1azovs1";
    }
    leaf volume-type {
      type string;
    }
    leaf volume-size {
      type uint32;
    }
    leaf root-dn {
      type string;
    }
    leaf netact-mrname {
      type string;
    }
    leaf netact-port {
      type string;
    }
    leaf netact-user {
      type string;
    }
    leaf netact-password {
      type string;
    }
    leaf netact-plmn {
      type string;
    }
    leaf netact-adaptation-release {
      type string;
    }
    leaf netact-ne-type {
      type string;
    }
    leaf http-port {
      type string;
    }
    leaf https-port {
      type string;
    }
    leaf da-port {
      type string;
    }
    leaf ssh-port {
      type string;
    }
    leaf da-meta-dir {
      type string;
    }
    leaf ip-version {
      type string;
    }
    leaf working-mode {
      type string;
    }
    leaf security-mode {
      type string;
    }
    leaf caf-trace-http-mode {
      type string;
    }
    leaf caf-trace-port {
      type string;
    }
    leaf tsp-process-node-http-mode {
      type string;
    }
    leaf tsp-process-node-port {
      type string;
    }
    leaf time-zone {
      type string;
    }
    leaf reposerver-hip {
      type string;
    }
    leaf reposerver-hip-http-port {
      type string;
    }
    leaf reposerver-hip-https-port {
      type string;
    }
    leaf reposerver-hip-security-mode {
      type string;
    }
    leaf def-passwd-root-user {
      type string;
    }
    leaf def-passwd-non-root-users {
      type string;
    }
  }

  grouping nokia-ims-cmrepo-unit-extensions {
    leaf repo-netact-instancename {
      description
        "CMRepo netact instance name";
      type identifier;
    }
  }

  grouping nokia-ims-sps-extensions {
    leaf hostname-prefix {
      type inet:host;
    }
    leaf sdc-config-data {
      description
        "JSON data used for service discovery and configuration.";
      units "json";
      type string;
    }
    list ntp-server {
      key hostname;
      leaf hostname {
        description "NTP server IP or name";
        type inet:host;
      }
      leaf version {
        description "NTP version";
        type string;
        mandatory true;
      }
      leaf preference {
        description "NTP server's preference indicator";
        type string;
        mandatory true;
      }
    }
    leaf localize-and-start-sps {
      type string;
    }
    leaf sps-auxiliary-mod {
      type string;
    }
    leaf time-zone {
      type string;
    }
  }

  grouping nokia-ims-sps-me-extensions {
    list comsvc-prefixes {
      key ip;
      leaf ip {
        type inet:ip-prefix;
      }
    }
  }

  grouping nokia-ims-dra-common-extensions {
    leaf aif {
      type string;
    }
    leaf ansible-param {
      type string;
    }
    leaf app-data-volume {
      type string;
    }
    leaf app-log-volume {
      type string;
    }
    leaf config-data-url {
      type string;
    }
    leaf db-server-address {
      type string;
    }
    leaf db-datastore-volume {
      type string;
    }
    leaf diameter-host {
      type string;
    }
    leaf diameter-realm {
      type string;
    }
    leaf geo-sitename {
      type string;
    }
    leaf hostname-prefix {
      type string;
    }
    leaf internal-prefix {
      type string;
    }
    leaf namespace-cfg {
      type string;
    }
    leaf ne-agent-dn {
      type string;
    }
    leaf ne-hostname {
      type string;
    }
    leaf ne-presentation-name {
      type string;
    }
    leaf netact-adaptation-release {
      type string;
    }
    leaf netact-address {
      type string;
    }
    leaf netact-mrname {
      type string;
    }
    leaf netact-ne-type {
      type string;
    }
    leaf netact-password {
      type string;
    }
    leaf natact-port {
      type string;
    }
    leaf netact-user {
      type string;
    }
    leaf oam-backup-volume {
      type string;
    }
    leaf oam-data-volume {
      type string;
    }
    leaf oam-log-volume {
      type string;
    }
    leaf oam-prometheus-volume {
      type string;
    }
    leaf sdc-config-data {
      type string;
    }
    leaf snmp-version {
      type string;
    }
    leaf time-zone {
      type string;
    }
    leaf vnf-network-config {
      type string;
    }
    leaf xdr-digest-log-file-size {
      type string;
    }
  }

  grouping nokia-ims-dra-dea-extensions {
    leaf address-group {
      type string;
    }
    leaf io-ips {
      type string;
    }
  }

  grouping nokia-ims-csd-sm-extensions {
    leaf internal-net-prefix {
      type string;
    }
  }

  grouping mavenir-rcs-cms-extensions {
    leaf bootup-time {
      type int32;
      description "The time to wait for a CMS VNF to bootup in seconds";
      reference "VNF parameter : BOOTUP_TIME";
      default 600;
    }
    leaf confd-mone-key-auth {
      type string;
      mandatory true;
      reference "VNFD parameter : CONFD_MONE_KEY_AUTH";
    }
    leaf confd-dsc-key-auth {
      type string;
      mandatory true;
      reference "VNFD parameter : CONFD_DSC_KEY_AUTH";
    }
    leaf confd-vnfm-key-auth {
      type string;
      mandatory true;
      reference "VNFD parameter : CONFD_VNFM_KEY_AUTH";
    }
    leaf confd-authentication {
      type string;
      mandatory true;
      reference "VNFD parameter : CONFD_AUTHENTICATION";
    }
    leaf confd-user-name {
      type string;
      mandatory true;
      reference "VNFD parameter : CONFD_USER_NAME";
    }
    leaf confd-user-passwd {
      type string;
      mandatory true;
      reference "VNFD parameter : CONFD_USER_PASSWD";
    }
    leaf installation-mode {
      type string;
      mandatory true;
      reference "VNFD parameter : INSTALLATION_MODE";
    }
	  leaf l1-http-enabled {
      type boolean;
      mandatory true;
      reference "VNFD parameter : LI_HTTP_ENABLED";
    }
    leaf l1-http-port {
      type string;
      mandatory true;
      reference "VNFD parameter : LI_HTTP_PORT";
    }
	  leaf oam-vip-support {
      type string;
      mandatory true;
      reference "VNFD parameter : OAM_VIP_SUPPORT";
    }
    leaf ssh-root-login {
      type string;
      mandatory true;
      reference "VNFD parameter : SSH_ROOT_LOGIN";
    }
  }

  grouping mavenir-rcs-sdns-extensions {
    leaf bootup-time {
      type int32;
      description "The time to wait for a sDNS VNF to bootup in seconds";
      reference "VNFD parameter : BOOTUP_TIME";
      default 600;
    }
    leaf cloud-profile-id {
      type string;
      mandatory true;
      reference "VNFD parameter : CLOUD_PROFILE_ID";
    }
    leaf ldaps-enabled {
      type boolean;
      mandatory true;
      reference "VNFD parameter : LDAPS_ENABLED";
    }
    leaf vnfm-fqdn {
      type string;
      mandatory true;
      reference "VNFD parameter : VNFM_FQDN";
    }
    leaf https-enabled {
      type boolean;
      mandatory true;
      reference "VNFD parameter : HTTPS_ENABLED";
    }
    leaf nsd-version {
      type string;
      mandatory true;
      reference "VNFD parameter : NSD_VERSION";
    }
    leaf vnfm-ttl {
      type int32;
      mandatory true;
      reference "VNFD parameter : VNFM_TTL";
    }
    leaf nsd-id {
      type int32;
      mandatory true;
      reference "VNFD parameter : NSD_ID";
    }
    leaf ssh-enabled {
      type boolean;
      mandatory true;
      reference "VNFD parameter : SSH_ENABLED";
    }
    leaf cms-ip-address1 {
      type inet:ip-address;
      mandatory true;
      reference "VNFD parameter : CMS_IP_ADDRESS1";
    }
	  leaf vnfd-version {
	    type string;
	    reference "VNFD parameter : VNFD_VERSION";
	  }
	  leaf vnfm-ip-address1 {
	    type inet:ip-address;
      mandatory true;
      reference "VNFD parameter : VNFM_IP_ADDRESS1";
    }
	  leaf vnfm-ip-address2 {
	    type inet:ip-address;
      mandatory true;
      reference "VNFD parameter : VNFM_IP_ADDRESS2";
    }
  }

  grouping mavenir-rcs-vnfm-prime-extensions {
    leaf bootup-time {
      type int32;
      description "The time to wait for a VNFM-P VNF to bootup in seconds";
      reference "VNF parameter : BOOTUP_TIME";
      default 600;
    }
    leaf dsc-vnf-confd-password {
      type string;
    }
    leaf dsc-vnf-confd-username {
      type string;
    }
    leaf enable-neutron-port-name-config {
      type string;
    }
    leaf enable-vm-name-config {
      type string;
    }
    leaf force-legacy-image-upload {
      type boolean;
    }
    leaf ip-type {
      type string;
      default "IPv6";
    }
    leaf mib-enabled {
      type boolean;
    }
    leaf nfvo-bootstrap-supported {
      type string;
    }
    leaf nfvo-https-required {
      type string;
    }
    leaf nfvo-ip {
      type string;
    }
    leaf nfvo-pkg-subsciption-supported {
      type boolean;
      default true;
    }
    leaf nfvo-port {
      type string;
    }
    leaf nfvo-present {
      type string;
    }
    leaf nfvo-vnf-instantiation-type {
      type string;
      default "VIM";
    }
    leaf notify-alarm {
      type boolean;
      default true;
    }
    leaf peer-vnfm-ip {
      type inet:ip-address;
    }
    leaf pull-img-from-vim {
      type boolean;
      default false;
    }
    leaf rebuild-retry-count{
      type int32;
      default 0;
    }
    leaf recreate-retry-count {
      type int32;
      default 0;
    }
    leaf restart-retry-count {
      type int32;
      default 0;
    }
    leaf root-login-disabled {
      type string;
    }
    leaf tosca-package-format {
      type string;
      default "tosca";
    }
    leaf tosca-package-language {
      type string;
      default "json";
    }
    leaf tosca-required {
      type boolean;
      default false;
    }
    leaf vdu-image-disk-format {
      type string;
      default "QCOW2";
    }
    leaf vdu-image-format {
      type string;
      default "BARE";
    }
    leaf vdu-image-min-disk-size {
      type int32;
      default 10;
    }
    leaf vdu-image-size {
      type string;
      default "1.73GB";
    }
    leaf vim-https-required {
      type boolean;
      default false;
    }
    leaf vim-present{
      type boolean;
      default true;
    }
    leaf vnf-confd-password {
      type string;
    }
    leaf vnf-confd-username {
      type string;
    }
    leaf vnf-https-required {
      type boolean;
      default false;
    }
    leaf vnfm-bootable-volume-size{
      type int32;
      default 50;
    }
    leaf vnfm-boot-vol-bus{
      type string;
      default ide;
    }
    leaf vnfm-boot-vol-id{
      type int32;
      default 1;
    }
    leaf vnfm-fqdn{
      type string;
    }
    leaf vnfm-ha{
      type boolean;
      default false;
    }
    leaf vnfm-mtu{
      type int32;
      default 0;
    }
  }

  grouping mavenir-rcs-wsg-extensions{
    uses rcs-common;
    leaf bootup-time {
      type int32;
      description "The time to wait for a VNFM-P VNF to bootup in seconds";
      default 600;
    }
    leaf cms-ip-address {
      type inet:ip-address;
      reference "VNF Parameter : CMS IP Address";
    }
    leaf dhcp-state {
      type boolean;
    }
    leaf https-enabled {
      type boolean;
    }
    leaf ldaps-enabled {
      type boolean;
    }
    leaf ssh-enabled {
      type boolean;
      default true;
    }
    leaf vnfm-ttl {
      type string;
    }
  }

  grouping rcs-common {
    leaf nsd-id{
      type string;
    }
    leaf nsd-version{
      type string;
    }
    leaf vnfm-ip-address{
      type inet:ip-address;
    }
    leaf vnfm-fqdn{
      type string;
    }
    leaf vnfm-port{
      type string;
    }
  }

  grouping mavenir-rcs-crdl-db-extensions {

	leaf cpu-num {
      type int32;
      mandatory true;
      reference "VNFD parameter : CPU_NUM";
      description "number of CPU required for this VNF";
    }
    leaf crdl-db-boot1-storage-size {
      type int32;
      mandatory true;
      reference "VNFD parameter : CRDL_DB_BOOT1_STORAGE_SIZE";
    }
    leaf crdl-db-boot1-vol-bus {
      type string;
      mandatory true;
      reference "VNFD parameter : CRDL_DB_BOOT1_VOL_BUS";
    }
    leaf crdl-db-bootup-time {
      type int32;
      description "The time to wait for a CRDL-DB VNF to bootup in seconds";
      reference "VNFD parameter : CRDL_DB_BOOTUP_TIME";
      default 600;
    }
    leaf crdl-db-db-replication-ipv6-platform {
          type boolean;
          reference "VNFD parameter : CRDL_DB_DB_REPLICATION_IPV6_Platform";
    }
    leaf crdl-db-db-traffic-ipv6-platform {
          type boolean;
          reference "VNFD parameter : CRDL_DB_DB_TRAFFIC_IPV6_Platform";
    }
    leaf crdl-db-image-min-disk-size {
      type int32;
      mandatory true;
      reference "VNFD parameter : CRDL_DB_IMAGE_MIN_DISK_SIZE";
    }
    leaf crdl-db-image-size {
          type string;
          reference "VNFD parameter : CRDL_DB_IMAGE_SIZE";
    }
    leaf crdl-db-storage-volume-size {
      type int32;
      mandatory true;
      reference "VNFD parameter : CRDL_DB_STORAGE_VOLUME_SIZE";
    }
    leaf crdl-db-sysadmin-password {
      tailf:suppress-echo "true";
      type tailf:aes-cfb-128-encrypted-string;
      reference "VNF parameter : CRDL_DB_SYSADMIN_PASSWORD";
    }
    leaf crdl-oam-ipv6-platform {
          type boolean;
          reference "VNFD parameter : CRDL_OAM_IPV6_Platform";
    }
    leaf crdl-opsuser-password {
      tailf:suppress-echo "true";
      type tailf:aes-cfb-128-encrypted-string;
      reference "VNFD parameter : CRDL_OPSUSER_PASSWORD";
    }
    leaf mem-size {
      type int32;
      mandatory true;
      reference "VNFD parameter : MEM_SIZE";
    }
    leaf ntp-configuration-needed {
          type boolean;
          reference "VNFD parameter : NTP_CONFIGURATION_NEEDED";
    }
    leaf ntp-servers {
          type inet:ip-address;
          reference "VNFD parameter : NTP_SERVERS";
    }
    leaf snmp-servers {
          type inet:ip-address;
          reference "VNFD parameter : SNMP_SERVERS";
    }
    leaf snmp-tool {
          type string;
          reference "VNFD parameter : SNMP_TOOL";
    }
    leaf ipv6 {
          type boolean;
          reference "VNFD parameter : IPV6";
    }
  }

  grouping f5-bigip-cgnat-extensions {
    leaf bootup-time {
      type int32;
      description "The time to wait for a CGNAT VNF to bootup in seconds";
      reference "VNF parameter : BOOTUP_TIME";
      default 600;
    }
    leaf vf5-adminpassword {
      type string;
      reference "VNFD parameter : VF5_ADMINPASSWORD";
    }
    leaf vf5-rootpassword {
      type string;
      reference "VNFD parameter : VF5_ROOTPASSWORD";
    }
    leaf zone-id {
      type string;
    }
  }

  grouping notif-service-info {
    leaf service-name {
      description "Affected Network Service.";
      type identifier;
    }
    leaf service-type {
      description "Type of Network Service.";
      type network-service-type;
    }
  }

  grouping notif-vnf {
    leaf type {
      description "Network Function Type";
      type network-function-type;
    }
    container esc {
      description "ESC managing this Network Function.";
      leaf ip {
        type inet:ip-address;
      }
      leaf name {
        type identifier;
      }
    }
    container location {
      leaf data-center {
        description "Data Center this Network Function is deployed at.";
        type identifier;
      }
      leaf pod {
        description "POD this Network Function is deployed at.";
        type identifier;
      }
    }
  }

  grouping notif-vm {
    leaf type {
      description "VDU type as defined in this Network Function's VNFD.";
      type identifier;
    }
    leaf vim-vm-id {
      description "ID of this VM in the managing VIM.";
      type identifier;
      // This can be found in:
      // /nfvo/internal/sol3-deployment-result/vnfcResourceInfo/computeResource/resourceId
    }
  }

  grouping network-service-notification {
    leaf operation {
      description "Operation Type";
      mandatory true;
      type enumeration {
        enum deploy;
        enum undeploy;
        enum heal;
        enum scale-in;
        enum scale-out;
        enum upgrade;
        enum rollback;
        enum start;
        enum stop;
        enum restart;
      }
    }
    leaf status {
      description "Operation State";
      mandatory true;
      type enumeration {
        enum init;
        enum done;
        enum fail;
      }
    }
    leaf event-time {
      description "Time this event happened.";
      type yang:date-and-time;
    }
    leaf info {
      description "Free form information about this event.";
      type string;
    }

    uses notif-service-info;

    list vnf {
      description "Affected Network Function";
      key name;
      leaf name {
        type identifier;
      }

      uses notif-vnf;

      list vm {
        description "Component VM of this Network Function";
        key hostname;
        leaf hostname {
          type inet:domain-name;
        }
        leaf internal-hostname {
          description "Internal hostname generated by the VNFM";
          type inet:domain-name;
        }
        leaf state {
          description "Current state of this VM.";
          type enumeration {
            enum running;
            enum stopped;
            enum rebooting;
            enum terminated;
          }
        }
        leaf esc-vm-id {
          description "ID of this VM in the managing ESC";
          // TODO: UUID?
          type identifier;
        }

        uses notif-vm;

      }
    }
  }

  grouping plan-notification {
    leaf service {
      type string;
    }
    leaf service-name {
      description "Affected Network Service.";
      type string;
    }
    leaf component {
      type string;
    }
    leaf component-type {
      type string;
    }
    leaf state {
      type string;
    }
    leaf status {
      type ncs:plan-state-status-t;
    }
    leaf error-info {
      type string;
    }
    leaf type {
      type enumeration {
        enum network-function;
        enum device-management;
        enum tor-switch;
      }
      default network-function;
    }
  }

  grouping rfs-network-function {
    leaf domain {
      type inet:domain-name;
      mandatory true;   // will always be set by e2e service
      description "
        Domain name used to construct Fully Qualified Domain Name by
        concatenating with VM hostname: <hostname>.<domain>";
    }
    leaf service-name {
      description "Network service deployment name.";
      type identifier;
    }
    leaf function-name {
      description "Network function name.";
      type identifier;
    }
    leaf instantiation-level {
      type identifier;
      default "default";
      description "
        Instantiation level defined in VNFD to use.
        This will determine number of VDUs are deployed.";
    }
    leaf deployment-flavor {
      type identifier;
      default "default";
      description "
        Deployment flavor defined in VNFD to use.
        Describes a specific deployment version of a VNF with specific
        requirements for capacity and performance.";
    }
    leaf hostname {
      type inet:domain-name;
      description
        "Hostname to use to communicate with this network function.
        Typically a hostname representing a virtual IP address
        shared between multiple units.";
    }
    leaf vnfd {
      mandatory true;
      type string;
      description "
        VNFD to use for this type of Network Function.
        Must be onboarded on target VIM.";
    }
    leaf license {
      description "
        License token to use for VNF if applicable.
        Default for can be configured in each VNF type.";
      // TODO: Define structure for defaults.
      type string;
    }
    leaf user {
      type identifier;
      description "
        Management login username specific to this VNF.
        Default values can be configured per VNF type.";
      // TODO: Model default value structure.
    }
    leaf password {
      tailf:suppress-echo "true";
      type tailf:aes-cfb-128-encrypted-string;
      description "Management login password specific to this VNF.";
    }
    leaf project {
      type string;
      description "Resource orchestration access-params project value";
    }
    container location {
      leaf data-center {
        description "Data Center this Network Function is deployed at.";
        type identifier;
      }
      leaf pod {
        description "POD this Network Function is deployed at.";
        type identifier;
      }
      container vnfm {
        description
          "VNFM Virtual Network Function Manager
          Cisco ESC or Nokia CBAM instance.";

        leaf name {
          mandatory true;
          type identifier;
          description "Hostname of VNFM";
        }
        leaf tenant {
          mandatory true;
          type identifier;
          description "Tenant to use when deploying VNFs";
        }
        leaf username {
          mandatory true;
          type identifier;
          description "Username to use when deploying VNFs";
        }
        leaf proxy-addresses { // VNFM_PROXY_ADDRS
          // Concat string from leaf-list with "," as separator
          type string;
        }
      }
    }

    list network {
      key type;
      leaf type {
        type identifier;
      }
      leaf name {
        type identifier;
        mandatory true;
      }
      leaf cidr {
        type ip-address-with-prefix;
      }
      leaf netmask {
        type inet:ip-address;
      }
      leaf extent {
        type network-extent;
      }
      leaf subnet-name {
        when "../extent='external'";
        type identifier;
        mandatory true;
      }
      leaf vlan-id {
        type uint16 {
          range "0..4096";
        }
      }
      leaf mtu {
        type uint16;
        units bytes;
        description "Maximum Transmission Unit";
      }
      leaf gateway {
        type inet:ip-address;
        description "Gateway IP Address for this subnet.";
      }
    }

    list connection-point {
      description
        "Connection point shared between multiple units using
        floating or virtual IP, as defined in the descriptor.";

      key name;
      leaf name {
        mandatory true;
        type rmno-common:identifier;
      }
      leaf management {
        type boolean;
        default false;
        description "If this is a management connection point.";
      }
      list ip {
        ordered-by user;
        description "
          IP address(es) to assign this network interface.
          Both IPv4 and IPv6 is possible to allow for dual-stack
          cases if this VNF requires it for Internet access.";

        key "address cidr";
        leaf address {
          type inet:ip-address;
        }
        leaf cidr {
          type uint8;
        }
        leaf type {
          type enumeration {
            enum "IPV4";
            enum "IPV6";
          }
          mandatory true;
        }
      }
      leaf-list security-group {
        type identifier;
        description "Security group(s) to apply to this network interface.";
      }
      leaf-list unit-types {
        type leafref {
          path "../../unit/type";
        }
      }
      leaf network {
          type string;
          description "Network used for this connection-point.";
      }
    }

    list unit {
      description "Virtual Deployment Unit, a single VM.";
      key hostname;
      leaf hostname {
        type inet:domain-name;
        mandatory true;
      }
      leaf type {
        description "VDU type as defined in the VNFD of this Network Function.";
        type identifier;
      }
      leaf image {
        type string;
        description "
          Image to use for this type of Network Function.
          Must be onboarded on target VIM.";
      }
      leaf flavor {
        mandatory true;
        type string;
        description "
          Flavor to use for this type of Network Function.
          Must be onboarded on target VIM.";
      }
      list connection-point {
        key name;
        description "
          Network connection point such as a network interface card,
          as defined in the descriptor.";
        leaf name {
          mandatory true;
          type identifier;
        }
        list ip {
          key address;
          ordered-by user;
          description "
            IP address(es) to assign this network interface.
            Both IPv4 and IPv6 is possible to allow for dual-stack
            cases if this VNF requires it for Internet access.";

          leaf address {
            type inet:ip-address;
          }
          leaf cidr {   // Because we need it in some places
            type uint8;
            mandatory true;
          }
          leaf type {
            type enumeration {
              enum "IPV4";
              enum "IPV6";
            }
            mandatory true;
          }
          leaf subnet-name {
            type string;
          }
        }
        list vip {
          key "address netmask";
          ordered-by user;
          description "
            Virtual IP address(es) to assign this network interface.
            Both IPv4 and IPv6 is possible to allow for dual-stack
            cases if this VNF requires it for Internet access.

            Setting this will populate allowed-address-pair list in the CVIM";

          leaf address {
            type inet:ip-address;
          }
          leaf netmask {
            type inet:ip-address;
          }
          leaf cidr {   // Because we need it in some places
            type uint8;
            mandatory true;
          }
        }
        leaf default-route {
          type inet:ip-address;
          description "Default route to use for this interface.";
        }
        leaf-list security-group {
          type identifier;
          description "Security group(s) to apply to this network interface.";
        }
        leaf port-security {
          type boolean;
          default false;
          description "If port security should be enabled.";
        }
        leaf management {
          type boolean;
          default false;
          description "If this is a management network interface.";
        }
        leaf network {
          type string;
          description "Network used for this connection-point.";
        }
      }
    }

    list dns {
      key type;
      leaf type {
        type dns-role;
      }
      leaf primary {
        mandatory true;
        type inet:ip-address;
      }
      leaf secondary {
        type inet:ip-address;
      }
    }

    leaf ntp {
     description "
      NTP server to use for Network Services deployed in this data center";
      type inet:host;
    }

    list extra-parameters {
      description "
        Extra parameters that will be passed on directly to Day 0 and
        Day 1 configuration templates.";
      key name;
      leaf name {
        type string {
          pattern "[A-Za-z0-9_]+";
        }
      }
      leaf value {
        type string;
      }
    }

    leaf init-failed {
      tailf:hidden rmno-internal;
      type empty;
    }
  }

  grouping notif-info {
    list notif-info {
      tailf:hidden rmno-internal;
      key name;
      leaf name {
        type identifier;
      }

      uses notif-service-info;

      list vnf {
        description "Affected Network Function";
        key name;
        leaf name {
          type identifier;
        }

        uses notif-vnf;

        list vm {
          description "Component VM of this Network Function";
          key hostname;
          leaf hostname {
            type inet:domain-name;
          }

          uses notif-vm;
        }
      }
    }
  }
}
